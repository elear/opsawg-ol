module ietf-owner-license {
  yang-version 1.1;
  namespace "urn:ietf:params:xml:ns:yang:ietf-owner-license";
  prefix ol;

  import ietf-inet-types {
    prefix inet;
    reference
      "RFC 6991: Common Yang Data Types, Section 4";
  }
  import ietf-mud {
    prefix ietf-mud;
    reference
      "RFC 8520: Manufacturer Usage Description Specification";
  }

  organization
    "IETF IOTOPS (IoT Operations) Working Group";
  contact
    "WG Web:   <http://datatracker.ietf.org/wg/iotops/>
     WG List:  <mailto:iotops@ietf.org>

     Editor:   Eliot Lear
               <mailto:lear@cisco.com>

     Editor:   Carsten Bormann
               <mailto:cabo@tzi.org>";
  description
    "This YANG module defines a grouping for expressing ownership
     and licensing information for YANG-described static objects,
     and augments the MUD model (RFC 8520) with that grouping.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX);
     see the RFC itself for full legal notices.";

  revision 2026-06-28 {
    description
      "Initial revision.";
    reference
      "RFC XXXX: Ownership and Licensing Statements in YANG";
  }

  grouping owner-license {
    description
      "A grouping expressing ownership and license information.";
    container owner-license {
      description
        "Container relating to ownership and licensing.";
      list license {
        key "owner-name";
        description
          "List of licenses that may be applied.";
        leaf owner-name {
          type string {
            length "1..128";
          }
          description
            "Name of the owner.";
        }
        choice license-type {
          mandatory true;
          description
            "Either choose a standard license type or point
             to one of your own.";
          case spdx {
            leaf-list spdx-tag {
              type string;
              min-elements 1;
              description
                "SPDX License Identifier.";
              reference
                "https://spdx.org/licenses/: SPDX License List";
            }
          }
          case url {
            leaf-list license-info {
              type inet:uri;
              min-elements 1;
              description
                "A URL pointing to licensing information.";
            }
          }
        }
      }
    }
  }

  augment "/ietf-mud:mud" {
    description
      "Add extension for ownership and licensing.";
    uses owner-license;
  }
}
