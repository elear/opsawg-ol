module ietf-ol {
  yang-version 1.1;
  namespace "urn:ietf:params:xml:ns:yang:ietf-ol";
  prefix ol;

  import ietf-inet-types {
    prefix inet;
  }
  
  import ietf-mud {
    prefix mud;
  }


  organization
    "IETF OPSAWG (Ops Area) Working Group";
  contact
    "WG
     Web: http://tools.ietf.org/wg/opsawg/
     WG List: opsawg@ietf.org
     Author: Eliot Lear lear@cisco.com
     Author: Carsten Bormann <cabo@tzi.org>";
  description
    "This YANG module to indicate ownership and licensing.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX);
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.  ";

  revision 2021-05-21 {
    description
      "Initial proposed standard.";
    reference
      "RFC XXXX: Extension for ownership and licensing";
  }

  grouping ol-extension {
    description
      "OL extension grouping";
    container ol {
      description
        "container relating to ownership and licensing.";
      leaf-list owners {
      type string;
        description
          "A list of owners, may be in the form of a copyright
           Example: Copyright (c) Jane Smith.  All rights Reserved.";
        }
      choice license-type {
        description "Either choose a standard license type or point
                     to one of your own.";
        case spdx-lt {
          leaf spdx-tag {
            type string;
            description "SPDX License Identifier, as indicated at
                         https://spdx.org/licenses/";
          }
        }
        case url {
          leaf license-info {
            type inet:uri;
            description "A URL pointing to licensing information.";
          }
        }
      }
    }
  }

  augment "/mud:mud" {
    description
      "Add extension for Ownership and licensing.";
    uses ol-extension;
  }
}
